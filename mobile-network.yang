module mobile-network {
    namespace "urn:tieto_course";

    prefix mobnet;

    typedef mobileNumber {
        type string {
            pattern "[+][3][8][0]([0-9]{9})";
        }
        description
          "Standart format for the Ukranian mobile number. ";
    }

    grouping user {
        leaf number {
            type mobileNumber;
        }
            
        leaf userName {
            type string;
        }
    }

    container users {
        list subscriber {
            key "number";

            description "Info about the subscriber";

            uses user;

            leaf incomingNumber {
                type mobileNumber;
                config true;
            }

            leaf state {
                config true;

		mandatory true;

                type enumeration {
                    enum idle {
                        value 1;
                        description
                            "Subscriber can accept calls";
                    }
                    enum busy {
                        value 2;
                        description
                            "Subscriber has a talk with another subscriber";
                    }
                    enum active {
                        value 3;
                        description
                            "Subsriber is calling or getting a call";
                    }
                }
            }
        }
    }
}
